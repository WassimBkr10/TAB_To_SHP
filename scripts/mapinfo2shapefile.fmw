FME workspace mapinfo2shapefile.fmw

Parameters:
- DestDataset_SHAPEFILE =
- FEATURE_TYPES =
- PARAMETER =
- SourceDataset_MAPINFO =

Readers:
- MAPINFO_1: MAPINFO from $(SourceDataset_MAPINFO)

Writers:
- SHAPEFILE_1: SHAPEFILE to $(DestDataset_SHAPEFILE)

DOC_URBA (reader MAPINFO_1)
    attributes: Idurba char(20), Typedoc char(4), Datappro char(8), Datefin char(8), Interco char(1), Siren char(9), Etat char(2), Nomreg char(80), Urlreg char(254), Nomplan char(80), Urlplan char(254), Siteweb char(254), Typeref char(2), Dateref char(8), Angle decimal(10,0), Datvalid char(8), Destdomi char(2), Insee char(5), Libelle char(254), Libelong char(254), Natecr char(40), Nattrac char(40), Nomfic char(80), Police char(40), Style char(40), Taille decimal(10,0), Txt char(80), Typeinf char(2), Typepsc char(2), Typezone char(3),
      Urlfic char(254)
    -> StringSearcher
StringSearcher
    CASE = no
    MATCHED_RESULT_ATTR = _first_match
    REGEXP = ^.*[^\w.TAB]
    STRING_TO_SEARCH = @Value(fme_dataset)
    MATCHED -> Shapefile1 (writer SHAPEFILE_1)
Shapefile1 (writer SHAPEFILE_1)
